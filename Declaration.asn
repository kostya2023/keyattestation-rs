AttestationModule DEFINITIONS ::= 
BEGIN

KeyDescription ::= SEQUENCE {
    attestationVersion         INTEGER,
    attestationSecurityLevel   SecurityLevel,
    keyMintVersion             INTEGER,
    keyMintSecurityLevel       SecurityLevel,
    attestationChallenge       OCTET STRING,
    uniqueId                   OCTET STRING,
    softwareEnforced           AuthorizationList,
    hardwareEnforced           AuthorizationList
}

SecurityLevel ::= ENUMERATED {
    software             (0),
    trustedenvironment   (1),
    strongbox            (2)
}

AuthorizationList ::= SEQUENCE {
    purpose                     [1] EXPLICIT SET OF INTEGER OPTIONAL,
    algorithm                   [2] EXPLICIT INTEGER OPTIONAL,
    keySize                     [3] EXPLICIT INTEGER OPTIONAL,
    blockMode                   [4] EXPLICIT SET OF INTEGER OPTIONAL,
    digest                      [5] EXPLICIT SET OF INTEGER OPTIONAL,
    padding                     [6] EXPLICIT SET OF INTEGER OPTIONAL,
    ecCurve                     [10] EXPLICIT INTEGER OPTIONAL,
    mlDsaVariant                [11] EXPLICIT INTEGER OPTIONAL,
    rsaPublicExponent           [200] EXPLICIT INTEGER OPTIONAL,
    rsaOaepMgfDigest            [203] EXPLICIT SET OF INTEGER OPTIONAL,
    activeDateTime              [400] EXPLICIT INTEGER OPTIONAL,
    originationExpireDateTime   [401] EXPLICIT INTEGER OPTIONAL,
    usageExpireDateTime         [402] EXPLICIT INTEGER OPTIONAL,
    usageCountLimit             [405] EXPLICIT INTEGER OPTIONAL,
    noAuthRequired              [503] EXPLICIT NULL OPTIONAL,
    userAuthType                [504] EXPLICIT INTEGER OPTIONAL,
    authTimeout                 [505] EXPLICIT INTEGER OPTIONAL,
    allowWhileOnBody            [506] EXPLICIT NULL OPTIONAL,
    trustedUserPresenceRequired [507] EXPLICIT NULL OPTIONAL,
    trustedConfirmationRequired [508] EXPLICIT NULL OPTIONAL,
    unlockedDeviceRequired      [509] EXPLICIT NULL OPTIONAL,
    creationDateTime            [701] EXPLICIT INTEGER OPTIONAL,
    origin                      [702] EXPLICIT INTEGER OPTIONAL,
    rollbackResistant           [703] EXPLICIT NULL OPTIONAL,
    rootOfTrust                 [704] EXPLICIT RootOfTrust OPTIONAL,
    osVersion                   [705] EXPLICIT INTEGER OPTIONAL,
    osPatchLevel                [706] EXPLICIT INTEGER OPTIONAL,
    attestationApplicationId    [709] EXPLICIT AttestationApplicationId OPTIONAL,
    attestationIdBrand          [710] EXPLICIT OCTET STRING OPTIONAL,
    attestationIdDevice         [711] EXPLICIT OCTET STRING OPTIONAL,
    attestationIdProduct        [712] EXPLICIT OCTET STRING OPTIONAL,
    attestationIdSerial         [713] EXPLICIT OCTET STRING OPTIONAL,
    attestationIdImei           [714] EXPLICIT OCTET STRING OPTIONAL,
    attestationIdMeid           [715] EXPLICIT OCTET STRING OPTIONAL,
    attestationIdManufacturer   [716] EXPLICIT OCTET STRING OPTIONAL,
    attestationIdModel          [717] EXPLICIT OCTET STRING OPTIONAL,
    vendorPatchLevel            [718] EXPLICIT INTEGER OPTIONAL,
    bootPatchLevel              [719] EXPLICIT INTEGER OPTIONAL,
    attestationIdSecondImei     [723] EXPLICIT OCTET STRING OPTIONAL,
    moduleHash                  [724] EXPLICIT OCTET STRING OPTIONAL
}

RootOfTrust ::= SEQUENCE {
    verifiedBootKey     OCTET STRING,
    deviceLocked        BOOLEAN,
    verifiedBootState   VerifiedBootState,
    verifiedBootHash    OCTET STRING OPTIONAL
}

VerifiedBootState ::= ENUMERATED {
    verified   (0),
    selfSigned (1),
    unverified (2),
    failed     (3)
}

AttestationApplicationId ::= SEQUENCE {
    packages    SET OF AttestationPackageInfo,
    signatures  SET OF OCTET STRING
}

AttestationPackageInfo ::= SEQUENCE {
    name     OCTET STRING, -- (UTF-8)
    version  INTEGER
}

ProvisioningInfoMap ::= OCTET STRING --CBOR Format

END
